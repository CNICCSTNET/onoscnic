module acme-system {
    namespace "http://acme.example.com/system";
    prefix "acme";
    organization "ACME Inc.";
    contact "joe@acme.example.com";
    description
        "The module for entities implementing the ACME system.";
    revision 2007-06-09 {
        description "Initial revision.";
    }
    container system {
        container login {
            leaf message {
                type string;
                description
                    "Message given at start of login session";
            }
        }
    }
}
